module ipfabric-types {
    yang-version "1.1";
    
    namespace "https://someurl.com/ipfabric-types.yang";
    
    prefix "ipf-types";
    
    description
      "This module contains data type definisions for IP CLOS fabric";
    
    revision "2018-05-07" {
      description
        "First revision";
      reference "1.0.0";
    }
    
    typedef intfname {
      type string {
        pattern '^(eth[0-9]+/[0-9]+)|po[0-9]+|vlan[0-9]{1,5}';
      }
    }
    
    typedef lag-type {
      type enumeration {
        enum LACP {
          description
            "Interfaces are aggregated with LACP";
        }
        enum STATIC {
          description
            "Interfaces are aggregated staticly";
        }
      }
    }
    
    typedef inttype {
      type enumeration {
        enum ethernetCsmacd {
          description
            "Ethernet interface";
        }
      
        enum l3ipvlan {
          description
            "Layer 3 Virtual LAN using IP.";
        }
        
        enum ieee8023adLag {
          description
            "IEEE 802.3ad Link Aggregate.";
        }
        
        enum softwareLoopback {
          description
            "Loopback interface";
        }
        
      }  
    }
    
   
    
    typedef as-number {
      type uint32 {
        range "1..4294967295";
      }
      description
         "AS number in as-plain notaion";
    }

}
